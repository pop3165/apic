module tailf-ned-odl-controller {
  namespace "http://tail-f.com/ned/odl-controller";
  prefix "odl-controller";

  import tailf-ncs {
    prefix ncs;
  }
  import tailf-common {
    prefix tailf;
  }
  import ietf-inet-types {
    prefix inet;
  }
  import ietf-yang-types {
    prefix yang;
  }
  revision "2015-07-02" {
    description
      "3.0.0
       Initial version.";
  }
  grouping TransportAddress {
    container TransportAddress {
      leaf ipAddress {
        type inet:ip-address;
        reference "http://www.iana.org/assignments/safi-namespace/safi-namespace.xhtml";
      }
      leaf port {
        type inet:port-number;
      }
    }
  }
  grouping template_ncs_TransportAddress {
    container TransportAddress {
      leaf ipAddress {
        type string;   // NCS patched all types to string
        reference "http://www.iana.org/assignments/safi-namespace/safi-namespace.xhtml";
      }
      leaf port {
        type string;   // NCS patched all types to string
      }
    }
  }
  grouping LispAFIAddress {
    leaf afi {
      type int16;
      reference "http://www.iana.org/assignments/safi-namespace/safi-namespace.xhtml";
    }
  }
  grouping template_ncs_LispAFIAddress {
    leaf afi {
      type string;   // NCS patched all types to string
      reference "http://www.iana.org/assignments/safi-namespace/safi-namespace.xhtml";
    }
  }
  grouping LispNoAddress {
    uses LispAFIAddress {
      refine "afi" {
        default "0";
      }
    }
  }
  grouping template_ncs_LispNoAddress {
    uses template_ncs_LispAFIAddress {
      refine "afi" {
        // NCS drop  (default) statement
      }
    }
  }
  grouping LispIpv4Address {
    uses LispAFIAddress {
      refine "afi" {
        default "1";
      }
    }
    leaf Ipv4Address {
      type inet:ipv4-address;
      reference "https://tools.ietf.org/html/rfc3209#section-4.6.2.1";
    }
  }
  grouping template_ncs_LispIpv4Address {
    uses template_ncs_LispAFIAddress {
      refine "afi" {
        // NCS drop  (default) statement
      }
    }
    leaf Ipv4Address {
      type string;   // NCS patched all types to string
      reference "https://tools.ietf.org/html/rfc3209#section-4.6.2.1";
    }
  }
  grouping LispIpv6Address {
    uses LispAFIAddress {
      refine "afi" {
        default "2";
      }
    }
    leaf Ipv6Address {
      type inet:ipv6-address;
    }
  }
  grouping template_ncs_LispIpv6Address {
    uses template_ncs_LispAFIAddress {
      refine "afi" {
        // NCS drop  (default) statement
      }
    }
    leaf Ipv6Address {
      type string;   // NCS patched all types to string
    }
  }
  grouping LispMacAddress {
    uses LispAFIAddress {
      refine "afi" {
        default "16389";
      }
    }
    leaf MacAddress {
      type yang:mac-address;
    }
  }
  grouping template_ncs_LispMacAddress {
    uses template_ncs_LispAFIAddress {
      refine "afi" {
        // NCS drop  (default) statement
      }
    }
    leaf MacAddress {
      type string;   // NCS patched all types to string
    }
  }
  grouping LispDistinguishedNameAddress {
    uses LispAFIAddress {
      refine "afi" {
        default "17";
      }
    }
    leaf distinguishedName {
      type string;
    }
  }
  grouping template_ncs_LispDistinguishedNameAddress {
    uses template_ncs_LispAFIAddress {
      refine "afi" {
        // NCS drop  (default) statement
      }
    }
    leaf distinguishedName {
      type string;   // NCS patched all types to string
    }
  }
  grouping LispASAddress {
    uses LispAFIAddress {
      refine "afi" {
        default "18";
      }
    }
    leaf AS {
      type int32;
    }
  }
  grouping template_ncs_LispASAddress {
    uses template_ncs_LispAFIAddress {
      refine "afi" {
        // NCS drop  (default) statement
      }
    }
    leaf AS {
      type string;   // NCS patched all types to string
    }
  }
  grouping LispSimpleAddress {
    choice primitiveAddress {
      case No {
        container NoAddress {
          uses LispNoAddress;
        }
      }
      case Ipv4 {
        container Ipv4Address {
          uses LispIpv4Address;
        }
      }
      case Ipv6 {
        container Ipv6Address {
          uses LispIpv6Address;
        }
      }
      case Mac {
        container MacAddress {
          uses LispMacAddress;
        }
      }
      case DistinguishedName {
        container DistinguishedNameAddress {
          uses LispDistinguishedNameAddress;
        }
      }
      case AS {
        container ASAddress {
          uses LispASAddress;
        }
      }
    }
  }
  grouping template_ncs_LispSimpleAddress {
    choice primitiveAddress {
      case No {
        container NoAddress {
          uses template_ncs_LispNoAddress;
        }
      }
      case Ipv4 {
        container Ipv4Address {
          uses template_ncs_LispIpv4Address;
        }
      }
      case Ipv6 {
        container Ipv6Address {
          uses template_ncs_LispIpv6Address;
        }
      }
      case Mac {
        container MacAddress {
          uses template_ncs_LispMacAddress;
        }
      }
      case DistinguishedName {
        container DistinguishedNameAddress {
          uses template_ncs_LispDistinguishedNameAddress;
        }
      }
      case AS {
        container ASAddress {
          uses template_ncs_LispASAddress;
        }
      }
    }
  }
  grouping ReencapHop {
    container hop {
      uses LispSimpleAddress;
    }
    leaf lookup {
      type boolean;
    }
    leaf RLOCProbe {
      type boolean;
    }
    leaf strict {
      type boolean;
    }
  }
  grouping template_ncs_ReencapHop {
    container hop {
      uses template_ncs_LispSimpleAddress;
    }
    leaf lookup {
      type string;   // NCS patched all types to string
    }
    leaf RLOCProbe {
      type string;   // NCS patched all types to string
    }
    leaf strict {
      type string;   // NCS patched all types to string
    }
  }
  grouping LispLcafAddress {
    uses LispAFIAddress {
      refine "afi" {
        default "16387";
      }
    }
    leaf lcafType {
      type uint8;
      reference "http://tools.ietf.org/html/draft-ietf-lisp-lcaf-03";
    }
  }
  grouping template_ncs_LispLcafAddress {
    uses template_ncs_LispAFIAddress {
      refine "afi" {
        // NCS drop  (default) statement
      }
    }
    leaf lcafType {
      type string;   // NCS patched all types to string
      reference "http://tools.ietf.org/html/draft-ietf-lisp-lcaf-03";
    }
  }
  grouping LcafSegmentAddress {
    reference "http://tools.ietf.org/html/draft-ietf-lisp-lcaf-08#section-4.1";
    uses LispLcafAddress {
      refine "lcafType" {
        default "2";
      }
    }
    leaf instanceId {
      type uint32 {
        range "0 .. 16777215";
      }
    }
    leaf iidMaskLength {
      type uint8;
    }
    container Address {
      uses LispSimpleAddress;
    }
  }
  grouping template_ncs_LcafSegmentAddress {
    reference "http://tools.ietf.org/html/draft-ietf-lisp-lcaf-08#section-4.1";
    uses template_ncs_LispLcafAddress {
      refine "lcafType" {
        // NCS drop  (default) statement
      }
    }
    leaf instanceId {
      type string;   // NCS patched all types to string
    }
    leaf iidMaskLength {
      type string;   // NCS patched all types to string
    }
    container Address {
      uses template_ncs_LispSimpleAddress;
    }
  }
  grouping LcafTrafficEngineeringAddress {
    reference "http://tools.ietf.org/html/draft-ietf-lisp-lcaf-09#section-4.9";
    uses LispLcafAddress {
      refine "lcafType" {
        default "10";
      }
    }
    list Hops {
      key "name";
      ordered-by "user";
      leaf name {
        type string;
      }
      uses ReencapHop;
    }
  }
  grouping template_ncs_LcafTrafficEngineeringAddress {
    reference "http://tools.ietf.org/html/draft-ietf-lisp-lcaf-09#section-4.9";
    uses template_ncs_LispLcafAddress {
      refine "lcafType" {
        // NCS drop  (default) statement
      }
    }
    list Hops {
      ordered-by "user";  // NCS patched to keep predictable order
      key "name";
      // NCS drop  (ordered-by) statement
      leaf name {
        type string;   // NCS patched all types to string
      }
      uses template_ncs_ReencapHop;
    }
  }
  grouping LcafListAddress {
    reference "http://tools.ietf.org/html/draft-ietf-lisp-lcaf-08#section-4.15.1";
    uses LispLcafAddress {
      refine "lcafType" {
        default "1";
      }
    }
    list Addresses {
      key "name";
      leaf name {
        type string;
      }
      uses LispSimpleAddress;
    }
  }
  grouping template_ncs_LcafListAddress {
    reference "http://tools.ietf.org/html/draft-ietf-lisp-lcaf-08#section-4.15.1";
    uses template_ncs_LispLcafAddress {
      refine "lcafType" {
        // NCS drop  (default) statement
      }
    }
    list Addresses {
      ordered-by "user";  // NCS patched to keep predictable order
      key "name";
      leaf name {
        type string;   // NCS patched all types to string
      }
      uses template_ncs_LispSimpleAddress;
    }
  }
  grouping LcafSourceDestAddress {
    reference "http://tools.ietf.org/html/draft-ietf-lisp-lcaf-08#section-4.11";
    uses LispLcafAddress {
      refine "lcafType" {
        default "12";
      }
    }
    container srcAddress {
      uses LispSimpleAddress;
    }
    container dstAddress {
      uses LispSimpleAddress;
    }
    leaf srcMaskLength {
      type uint8;
    }
    leaf dstMaskLength {
      type uint8;
    }
  }
  grouping template_ncs_LcafSourceDestAddress {
    reference "http://tools.ietf.org/html/draft-ietf-lisp-lcaf-08#section-4.11";
    uses template_ncs_LispLcafAddress {
      refine "lcafType" {
        // NCS drop  (default) statement
      }
    }
    container srcAddress {
      uses template_ncs_LispSimpleAddress;
    }
    container dstAddress {
      uses template_ncs_LispSimpleAddress;
    }
    leaf srcMaskLength {
      type string;   // NCS patched all types to string
    }
    leaf dstMaskLength {
      type string;   // NCS patched all types to string
    }
  }
  grouping LcafKeyValueAddress {
    reference "http://tools.ietf.org/html/draft-ietf-lisp-lcaf-08#section-4.14";
    uses LispLcafAddress {
      refine "lcafType" {
        default "15";
      }
    }
    container key {
      uses LispSimpleAddress;
    }
    container value {
      uses LispSimpleAddress;
    }
  }
  grouping template_ncs_LcafKeyValueAddress {
    reference "http://tools.ietf.org/html/draft-ietf-lisp-lcaf-08#section-4.14";
    uses template_ncs_LispLcafAddress {
      refine "lcafType" {
        // NCS drop  (default) statement
      }
    }
    container key {
      uses template_ncs_LispSimpleAddress;
    }
    container value {
      uses template_ncs_LispSimpleAddress;
    }
  }
  grouping LcafApplicationDataAddress {
    reference "http://tools.ietf.org/html/draft-ietf-lisp-lcaf-08#section-4.3";
    uses LispLcafAddress {
      refine "lcafType" {
        default "4";
      }
    }
    container Address {
      uses LispSimpleAddress;
    }
    leaf protocol {
      type uint8;
    }
    leaf ipTos {
      type int32;
    }
    leaf localPortLow {
      type inet:port-number;
    }
    leaf localPortHigh {
      type inet:port-number;
    }
    leaf remotePortLow {
      type inet:port-number;
    }
    leaf remotePortHigh {
      type inet:port-number;
    }
  }
  grouping template_ncs_LcafApplicationDataAddress {
    reference "http://tools.ietf.org/html/draft-ietf-lisp-lcaf-08#section-4.3";
    uses template_ncs_LispLcafAddress {
      refine "lcafType" {
        // NCS drop  (default) statement
      }
    }
    container Address {
      uses template_ncs_LispSimpleAddress;
    }
    leaf protocol {
      type string;   // NCS patched all types to string
    }
    leaf ipTos {
      type string;   // NCS patched all types to string
    }
    leaf localPortLow {
      type string;   // NCS patched all types to string
    }
    leaf localPortHigh {
      type string;   // NCS patched all types to string
    }
    leaf remotePortLow {
      type string;   // NCS patched all types to string
    }
    leaf remotePortHigh {
      type string;   // NCS patched all types to string
    }
  }
  grouping LispAddress {
    container LispAddressContainer {
      choice Address {
        case No {
          container NoAddress {
            uses LispNoAddress;
          }
        }
        case Ipv4 {
          container Ipv4Address {
            uses LispIpv4Address;
          }
        }
        case Ipv6 {
          container Ipv6Address {
            uses LispIpv6Address;
          }
        }
        case Mac {
          container MacAddress {
            uses LispMacAddress;
          }
        }
        case DistinguishedName {
          container distinguishedName {
            uses LispDistinguishedNameAddress;
          }
        }
        case AS {
          container AS {
            uses LispASAddress;
          }
        }
        case LcafSegment {
          container LcafSegmentAddr {
            uses LcafSegmentAddress;
          }
        }
        case LcafSourceDest {
          container LcafSourceDestAddr {
            uses LcafSourceDestAddress;
          }
        }
        case LcafKeyValue {
          container LcafKeyValueAddressAddr {
            uses LcafKeyValueAddress;
          }
        }
        case LcafList {
          container LcafListAddr {
            uses LcafListAddress;
          }
        }
        case LcafApplicationData {
          container LcafApplicationDataAddr {
            uses LcafApplicationDataAddress;
          }
        }
        case LcafTrafficEngineering {
          container LcafTrafficEngineeringAddr {
            uses LcafTrafficEngineeringAddress;
          }
        }
      }
    }
  }
  grouping template_ncs_LispAddress {
    container LispAddressContainer {
      choice Address {
        case No {
          container NoAddress {
            uses template_ncs_LispNoAddress;
          }
        }
        case Ipv4 {
          container Ipv4Address {
            uses template_ncs_LispIpv4Address;
          }
        }
        case Ipv6 {
          container Ipv6Address {
            uses template_ncs_LispIpv6Address;
          }
        }
        case Mac {
          container MacAddress {
            uses template_ncs_LispMacAddress;
          }
        }
        case DistinguishedName {
          container distinguishedName {
            uses template_ncs_LispDistinguishedNameAddress;
          }
        }
        case AS {
          container AS {
            uses template_ncs_LispASAddress;
          }
        }
        case LcafSegment {
          container LcafSegmentAddr {
            uses template_ncs_LcafSegmentAddress;
          }
        }
        case LcafSourceDest {
          container LcafSourceDestAddr {
            uses template_ncs_LcafSourceDestAddress;
          }
        }
        case LcafKeyValue {
          container LcafKeyValueAddressAddr {
            uses template_ncs_LcafKeyValueAddress;
          }
        }
        case LcafList {
          container LcafListAddr {
            uses template_ncs_LcafListAddress;
          }
        }
        case LcafApplicationData {
          container LcafApplicationDataAddr {
            uses template_ncs_LcafApplicationDataAddress;
          }
        }
        case LcafTrafficEngineering {
          container LcafTrafficEngineeringAddr {
            uses template_ncs_LcafTrafficEngineeringAddress;
          }
        }
      }
    }
  }
  grouping EidRecords {
    list EidRecord {
      uses LispAddress;
      leaf mask {
        type uint8;
      }
    }
  }
  grouping template_ncs_EidRecords {
    list EidRecord {
      ordered-by "user";  // NCS patched to keep predictable order
      uses template_ncs_LispAddress;
      leaf mask {
        type string;   // NCS patched all types to string
      }
    }
  }
  grouping LocatorRecords {
    list LocatorRecord {
      key "name";
      leaf name {
        type string;
      }
      leaf priority {
        type uint8;
      }
      leaf weight {
        type uint8;
      }
      leaf multicastPriority {
        type uint8;
      }
      leaf multicastWeight {
        type uint8;
      }
      leaf localLocator {
        type boolean;
      }
      leaf rlocProbed {
        type boolean;
      }
      leaf routed {
        type boolean;
      }
      uses LispAddress;
    }
  }
  grouping template_ncs_LocatorRecords {
    list LocatorRecord {
      ordered-by "user";  // NCS patched to keep predictable order
      key "name";
      leaf name {
        type string;   // NCS patched all types to string
      }
      leaf priority {
        type string;   // NCS patched all types to string
      }
      leaf weight {
        type string;   // NCS patched all types to string
      }
      leaf multicastPriority {
        type string;   // NCS patched all types to string
      }
      leaf multicastWeight {
        type string;   // NCS patched all types to string
      }
      leaf localLocator {
        type string;   // NCS patched all types to string
      }
      leaf rlocProbed {
        type string;   // NCS patched all types to string
      }
      leaf routed {
        type string;   // NCS patched all types to string
      }
      uses template_ncs_LispAddress;
    }
  }
  grouping EidToLocatorRecord {
    leaf recordTtl {
      type int32;
    }
    leaf maskLength {
      type uint8;
    }
    leaf mapVersion {
      type int16;
    }
    leaf action {
      type enumeration {
        enum "NoAction";
        enum "NativelyForward";
        enum "SendMapRequest";
        enum "Drop";
      }
    }
    leaf authoritative {
      type boolean;
    }
    uses LispAddress;
    uses LocatorRecords;
  }
  grouping template_ncs_EidToLocatorRecord {
    leaf recordTtl {
      type string;   // NCS patched all types to string
    }
    leaf maskLength {
      type string;   // NCS patched all types to string
    }
    leaf mapVersion {
      type string;   // NCS patched all types to string
    }
    leaf action {
      type string;   // NCS patched all types to string
    }
    leaf authoritative {
      type string;   // NCS patched all types to string
    }
    uses template_ncs_LispAddress;
    uses template_ncs_LocatorRecords;
  }
  grouping EidToLocatorRecords {
    list eidToLocatorRecord {
      uses EidToLocatorRecord;
    }
  }
  grouping template_ncs_EidToLocatorRecords {
    list eidToLocatorRecord {
      ordered-by "user";  // NCS patched to keep predictable order
      uses template_ncs_EidToLocatorRecord;
    }
  }
  grouping xtrSiteId {
    leaf xtrId {
      type binary;
    }
    leaf siteId {
      type binary;
    }
  }
  grouping template_ncs_xtrSiteId {
    leaf xtrId {
      type string;   // NCS patched all types to string
    }
    leaf siteId {
      type string;   // NCS patched all types to string
    }
  }
  grouping MapRegister {
    reference "http://tools.ietf.org/html/rfc6830#section-6.1.6, http://tools.ietf.org/html/draft-ermagan-lisp-nat-traversal-05#section-4.3";
    leaf proxyMapReply {
      type boolean;
    }
    leaf xtrSiteIdPresent {
      type boolean;
    }
    leaf wantMapNotify {
      type boolean;
    }
    leaf nonce {
      type int64;
    }
    leaf keyId {
      type int16;
    }
    leaf authenticationData {
      type binary;
    }
    uses EidToLocatorRecords;
    uses xtrSiteId;
  }
  grouping template_ncs_MapRegister {
    reference "http://tools.ietf.org/html/rfc6830#section-6.1.6, http://tools.ietf.org/html/draft-ermagan-lisp-nat-traversal-05#section-4.3";
    leaf proxyMapReply {
      type string;   // NCS patched all types to string
    }
    leaf xtrSiteIdPresent {
      type string;   // NCS patched all types to string
    }
    leaf wantMapNotify {
      type string;   // NCS patched all types to string
    }
    leaf nonce {
      type string;   // NCS patched all types to string
    }
    leaf keyId {
      type string;   // NCS patched all types to string
    }
    leaf authenticationData {
      type string;   // NCS patched all types to string
    }
    uses template_ncs_EidToLocatorRecords;
    uses template_ncs_xtrSiteId;
  }
  grouping MapNotify {
    reference "http://tools.ietf.org/html/rfc6830#section-6.1.7 , http://tools.ietf.org/html/draft-ermagan-lisp-nat-traversal-05#section-4.3";
    leaf xtrSiteIdPresent {
      type boolean;
    }
    leaf nonce {
      type int64;
    }
    leaf keyId {
      type int16;
    }
    leaf authenticationData {
      type binary;
    }
    uses EidToLocatorRecords;
    uses xtrSiteId;
  }
  grouping template_ncs_MapNotify {
    reference "http://tools.ietf.org/html/rfc6830#section-6.1.7 , http://tools.ietf.org/html/draft-ermagan-lisp-nat-traversal-05#section-4.3";
    leaf xtrSiteIdPresent {
      type string;   // NCS patched all types to string
    }
    leaf nonce {
      type string;   // NCS patched all types to string
    }
    leaf keyId {
      type string;   // NCS patched all types to string
    }
    leaf authenticationData {
      type string;   // NCS patched all types to string
    }
    uses template_ncs_EidToLocatorRecords;
    uses template_ncs_xtrSiteId;
  }
  grouping MapRequest {
    reference "http://tools.ietf.org/html/rfc6830#section-6.1.2";
    leaf authoritative {
      type boolean;
    }
    leaf mapDataPresent {
      type boolean;
    }
    leaf probe {
      type boolean;
    }
    leaf smr {
      type boolean;
    }
    leaf pitr {
      type boolean;
    }
    leaf smrInvoked {
      type boolean;
    }
    leaf nonce {
      type int64;
    }
    container SourceEid {
      uses LispAddress;
    }
    list itrRloc {
      uses LispAddress;
    }
    uses EidRecords;
    container MapReply {
      uses EidToLocatorRecord;
    }
  }
  grouping template_ncs_MapRequest {
    reference "http://tools.ietf.org/html/rfc6830#section-6.1.2";
    leaf authoritative {
      type string;   // NCS patched all types to string
    }
    leaf mapDataPresent {
      type string;   // NCS patched all types to string
    }
    leaf probe {
      type string;   // NCS patched all types to string
    }
    leaf smr {
      type string;   // NCS patched all types to string
    }
    leaf pitr {
      type string;   // NCS patched all types to string
    }
    leaf smrInvoked {
      type string;   // NCS patched all types to string
    }
    leaf nonce {
      type string;   // NCS patched all types to string
    }
    container SourceEid {
      uses template_ncs_LispAddress;
    }
    list itrRloc {
      ordered-by "user";  // NCS patched to keep predictable order
      uses template_ncs_LispAddress;
    }
    uses template_ncs_EidRecords;
    container MapReply {
      uses template_ncs_EidToLocatorRecord;
    }
  }
  grouping MapReply {
    reference "http://tools.ietf.org/html/rfc6830#section-6.1.4";
    leaf probe {
      type boolean;
    }
    leaf nonce {
      type int64;
    }
    leaf echoNonceEnabled {
      type boolean;
    }
    leaf securityEnabled {
      type boolean;
    }
    uses EidToLocatorRecords;
  }
  grouping template_ncs_MapReply {
    reference "http://tools.ietf.org/html/rfc6830#section-6.1.4";
    leaf probe {
      type string;   // NCS patched all types to string
    }
    leaf nonce {
      type string;   // NCS patched all types to string
    }
    leaf echoNonceEnabled {
      type string;   // NCS patched all types to string
    }
    leaf securityEnabled {
      type string;   // NCS patched all types to string
    }
    uses template_ncs_EidToLocatorRecords;
  }
  grouping MapRegisterNotification {
    container MapRegister {
      uses MapRegister;
    }
    uses TransportAddress;
  }
  grouping template_ncs_MapRegisterNotification {
    container MapRegister {
      uses template_ncs_MapRegister;
    }
    uses template_ncs_TransportAddress;
  }
  grouping MapNotifyMessage {
    container MapNotify {
      uses MapNotify;
    }
    uses TransportAddress;
  }
  grouping template_ncs_MapNotifyMessage {
    container MapNotify {
      uses template_ncs_MapNotify;
    }
    uses template_ncs_TransportAddress;
  }
  grouping MapRequestMessage {
    container MapRequest {
      uses MapRequest;
    }
    uses TransportAddress;
  }
  grouping template_ncs_MapRequestMessage {
    container MapRequest {
      uses template_ncs_MapRequest;
    }
    uses template_ncs_TransportAddress;
  }
  grouping MapRequestNotification {
    container MapRequest {
      uses MapRequest;
    }
    uses TransportAddress;
  }
  grouping template_ncs_MapRequestNotification {
    container MapRequest {
      uses template_ncs_MapRequest;
    }
    uses template_ncs_TransportAddress;
  }
  grouping MapReplyMessage {
    container MapReply {
      uses MapReply;
    }
    uses TransportAddress;
  }
  grouping template_ncs_MapReplyMessage {
    container MapReply {
      uses template_ncs_MapReply;
    }
    uses template_ncs_TransportAddress;
  }
  grouping MapReplyNotification {
    container MapReply {
      uses MapReply;
    }
  }
  grouping template_ncs_MapReplyNotification {
    container MapReply {
      uses template_ncs_MapReply;
    }
  }
  grouping lisp-prefix {
    uses LispAddress;
    leaf mask-length {
      type uint8;
    }
  }
  grouping template_ncs_lisp-prefix {
    uses template_ncs_LispAddress;
    leaf mask-length {
      type string;   // NCS patched all types to string
    }
  }
  grouping mapping-authkey {
    leaf key-type {
      type uint16;
    }
    leaf authkey {
      type string;
    }
  }
  grouping template_ncs_mapping-authkey {
    leaf key-type {
      type string;   // NCS patched all types to string
    }
    leaf authkey {
      type string;   // NCS patched all types to string
    }
  }
  grouping db-instance {
    description "Describes the mappings belonging to the same Instance ID";
    leaf iid {
      description "The 24-bit Instance ID";
      type iid-uri;
    }
    list mapping {
      description "A list of EID-to-RLOC mappings within the same Instance ID";
      key "eid origin";
      leaf eid {
        type eid-uri;
      }
      leaf origin {
        type mapping-origin;
      }
      uses EidToLocatorRecord;
    }
    list authentication-key {
      description "A list of authentication keys for EID prefixes within the same Instance ID";
      key "eid";
      leaf eid {
        type eid-uri;
      }
      uses lisp-prefix;
      uses mapping-authkey;
    }
  }
  grouping template_ncs_db-instance {
    description "Describes the mappings belonging to the same Instance ID";
    leaf iid {
      description "The 24-bit Instance ID";
      type string;   // NCS patched all types to string
    }
    list mapping {
      ordered-by "user";  // NCS patched to keep predictable order
      description "A list of EID-to-RLOC mappings within the same Instance ID";
      key "eid origin";
      leaf eid {
        type string;   // NCS patched all types to string
      }
      leaf origin {
        type string;   // NCS patched all types to string
      }
      uses template_ncs_EidToLocatorRecord;
    }
    list authentication-key {
      ordered-by "user";  // NCS patched to keep predictable order
      description "A list of authentication keys for EID prefixes within the same Instance ID";
      key "eid";
      leaf eid {
        type string;   // NCS patched all types to string
      }
      uses template_ncs_lisp-prefix;
      uses template_ncs_mapping-authkey;
    }
  }
  identity instance-id-context {
    description "A classifier for instance-id elements which allows direct access to a particular element in the data tree.";
  }
  identity eid-context {
    description "A classifier for endpoint-id elements which allows direct access to a particular element in the data tree.";
  }
  typedef mapping-origin {
    description "The originating entity of an EID-to-RLOC mapping";
    type enumeration {
      enum "northbound";
      enum "southbound";
    }
  }
  typedef iid-uri {
    description "IID as a string lookup key in a URI";
    type inet:uri;
  }
  typedef eid-uri {
    description "EID as a string lookup key in a URI";
    type inet:uri;
  }
  augment /ncs:devices/ncs:device/ncs:rpc {
    container rpc-add-key {
      tailf:action add-key {
        tailf:actionpoint ncsproxy {
              tailf:internal;
        }
        input {
          uses lisp-prefix;
          uses mapping-authkey;
        }
        output {
          leaf result {
            type string;
          }
        }
      }
   }
   }
  augment /ncs:devices/ncs:device/ncs:rpc {
    container rpc-get-key {
      tailf:action get-key {
        tailf:actionpoint ncsproxy {
              tailf:internal;
        }
        input {
          uses lisp-prefix;
        }
        output {
          leaf result {
            type string;
          }
          leaf output {
            type string;
          }
        }
      }
   }
   }
  augment /ncs:devices/ncs:device/ncs:rpc {
    container rpc-update-key {
      tailf:action update-key {
        tailf:actionpoint ncsproxy {
              tailf:internal;
        }
        input {
          container eid {
            uses lisp-prefix;
          }
          container key {
            uses mapping-authkey;
          }
        }
        output {
          leaf result {
            type string;
          }
        }
      }
   }
   }
  augment /ncs:devices/ncs:device/ncs:rpc {
    container rpc-remove-key {
      tailf:action remove-key {
        tailf:actionpoint ncsproxy {
              tailf:internal;
        }
        input {
          uses lisp-prefix;
        }
        output {
          leaf result {
            type string;
          }
        }
      }
   }
   }
  augment /ncs:devices/ncs:device/ncs:rpc {
    container rpc-add-mapping {
      tailf:action add-mapping {
        tailf:actionpoint ncsproxy {
              tailf:internal;
        }
        input {
          uses EidToLocatorRecord;
        }
        output {
          leaf result {
            type string;
          }
        }
      }
   }
   }
  augment /ncs:devices/ncs:device/ncs:rpc {
    container rpc-get-mapping {
      tailf:action get-mapping {
        tailf:actionpoint ncsproxy {
              tailf:internal;
        }
        input {
          uses lisp-prefix;
        }
        output {
          leaf result {
            type string;
          }
          leaf output {
            type string;
          }
        }
      }
   }
   }
  augment /ncs:devices/ncs:device/ncs:rpc {
    container rpc-update-mapping {
      tailf:action update-mapping {
        tailf:actionpoint ncsproxy {
              tailf:internal;
        }
        input {
          uses EidToLocatorRecord;
        }
        output {
          leaf result {
            type string;
          }
        }
      }
   }
   }
  augment /ncs:devices/ncs:device/ncs:rpc {
    container rpc-remove-mapping {
      tailf:action remove-mapping {
        tailf:actionpoint ncsproxy {
              tailf:internal;
        }
        input {
          uses lisp-prefix;
        }
        output {
          leaf result {
            type string;
          }
        }
      }
   }
   }
  augment /ncs:devices/ncs:device/ncs:config {
  }
  augment /ncs:devices/ncs:template/ncs:config {
  }

  // Skip entire stats tree due to --ncs-skip-statistics flag

}
