module tailf-ned-odl-controller-id {
  namespace "http://tail-f.com/ned/odl-controller-id";
  prefix "odl-controller-id";

  import tailf-common {
    prefix tailf;
  }
  import tailf-ncs {
    prefix ncs;
  }
  import tailf-ncs-ned {
    prefix ned;
  }
  identity odl-controller {
    base ned:generic-ned-id;
  }
  augment /ncs:devices/ncs:device/ncs:config {
  }
  augment /ncs:devices/ncs:template/ncs:config {
  }

  // Skip entire stats tree due to --ncs-skip-statistics flag

}
