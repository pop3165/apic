module tailf-ned-cisco-ios-xr-id {
  namespace "http://tail-f.com/ned/cisco-ios-xr-id";
  prefix "cisco-ios-xr-id";

  import tailf-common {
    prefix tailf;
  }
  import tailf-ncs {
    prefix ncs;
  }
  import tailf-ncs-ned {
    prefix ned;
  }
  identity cisco-ios-xr {
    base ned:cli-ned-id;
  }
  augment /ncs:devices/ncs:device/ncs:config {
  }
  augment /ncs:devices/ncs:template/ncs:config {
  }

  // Skip entire stats tree due to --ncs-skip-statistics flag

}
