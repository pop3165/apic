/*
Copyright @ 2015 <Cisco China Team>
   This project is maintained by Cisco China Team.
   Team members:
   		Yuanchao Su  : yuasu@cisco.com
		Fan Yang     : fyang2@cisco.com
		Qing Zhong   : qinzhong@cisco.com
		Zichuan Ma   : zicma@cisco.com
		Yinsong Xue  : yinsxue@cisco.com
		Xinyi Xu     : xinysu@cisco.com

This part of code is written by Zichuan Ma & Yinsong Xue and is maintained by Yinsong (yinsxue).
For further information, please contact Yinsong Xue (yinsxue@cisco.com) or Yuanchao Su(yuasu@cisco.com)
*/

/*
The Yang Model for the following RPCs has been implemented：
1. add/update/remove a LSP (add-lsp update-lsp remove-lsp)
2. add/update/remove a Segment routing LSP (add-lsp-sr update-lsp-sr remove-lsp-sr)

The corresponding REST post can be found in https://wiki.opendaylight.org/view/BGP_LS_PCEP:Helium_Operations_Guide .

Sample ncs calls:
1. add-lsp
devices device odlc rpc rpc-add-lsp add-lsp name examplelsp node pcc://192.168.0.1 network-topology pcep-topology arguments { lsp { administrative true delegate true } endpoints-obj { ipv4 { source-ipv4-address 192.168.0.1 destination-ipv4-address 192.168.0.3 } } ero { subobject { ip-prefix 10.0.0.6/32 loose false } } }
2. add-lsp-sr
devices device odlc rpc rpc-add-lsp-sr add-lsp-sr name update-tunnel node pcc://172.16.1.158 network-topology pcep-topology arguments { lsp { administrative true delegate true } path-setup-type { pst 1 } endpoints-obj { ipv4 { source-ipv4-address 192.168.0.1 destination-ipv4-address 192.168.0.2 } } ero { subobject { loose false sid-type ipv4-node-id m-flag true sid 16002 ip-address 192.168.0.2 } } } 
3. update-lsp-sr
devices device odlc rpc rpc-update-lsp-sr update-lsp-sr node pcc://172.16.1.158 name update-tunnel arguments { lsp { delegate true administrative true } path-setup-type { pst 1 } ero { subobject { loose false sid-type ipv4-node-id m-flag true sid 16003 ip-address 192.168.0.3 } subobject { loose false sid-type ipv4-node-id m-flag true sid 16002 ip-address 192.168.0.2 } } } network-topology pcep-topology
4. remove-lsp-sr
devices device odlc rpc rpc-remove-lsp-sr remove-lsp-sr node pcc://172.16.1.158 name update-tunnel network-topology pcep-topology 

*/
module odl {
  namespace "http://tail-f.com/ned/odl";
  prefix odl;

  import tailf-ncs-ned {
    prefix ned;
  }

  import tailf-common {
    prefix tailf;
  }
  
  import ietf-inet-types {
	prefix inet;
  }

  identity odl-id {
    base ned:generic-ned-id;
  }

  typedef pcc-sync-state {
      type enumeration {
          enum initial-resync {
              description
                  "Initial state resynchronization is being performed.";
          }
          enum synchronized {
              description
                  "State synchronization has been achieved.";
          }
      }
  }
  
  grouping pcep-client-attributes {
      container path-computation-client {
          leaf ip-address {
              type inet:ip-address;
          }
          container stateful-tlv {
        	  container stateful {
        		  leaf initiation {
        			  type boolean;
        		  }
        		  leaf lsp-update-capability {
        			  type boolean;
        		  }
        	  }
          }
          leaf state-sync {
              type pcc-sync-state;
              when "../stateful-tlv";
          }
          list reported-lsp {
              leaf name {
                  type string;
              }
              key name;
              list path {
                  leaf lsp-id {
                      type uint32;
                      mandatory true;
                  }
                  key lsp-id;
                  /*
                  uses explicit-route-object;
                  */
                  uses lsp-attributes;
              }
          }
      }
  }

  list pcep-topology {
  	key topology-id;
	leaf topology-id {
      type string;
	}
	
	list node {
	  leaf node-id {
		type string;
      }
      key node-id;
      uses pcep-client-attributes;
    }
  }
  
  grouping reported-route-object {
  }
  
  grouping lsp-id {
      leaf node {
          type string;
          mandatory true;
      }
      leaf name {
          type string;
          mandatory true;
      }
  }
  
  grouping lsp-attributes {
	  container lsp {
		  leaf delegate {
			  type boolean;
			  mandatory true;
		  }
		  leaf administrative {
			  type boolean;
			  mandatory true;
		  }
	  }
  }
  
  grouping endpoints-object {
	  container endpoints-obj {
		  choice address-family {
	          mandatory true;
	          case ipv4-case {
	              container ipv4 {
	                  leaf source-ipv4-address {
	                      type inet:ipv4-address;
	                      mandatory true;
	                  }
	
	                  leaf destination-ipv4-address {
	                      type inet:ipv4-address;
	                      mandatory true;
	                  }
	              }
	          }
	          case ipv6-case {
	              container ipv6 {
	                  leaf source-ipv6-address {
	                      type inet:ipv6-address;
	                      mandatory true;
	                  }
	
	                  leaf destination-ipv6-address {
	                      type inet:ipv6-address;
	                      mandatory true;
	                  }
	              }
	          }
		  }
	  }
  }
  
  grouping explicit-route-object {
      container ero {
          list subobject {
        	  min-elements 1;
              leaf loose {
                  type boolean;
                  mandatory true;
              }
              leaf ip-prefix {
            	  type inet:ip-prefix;
            	  mandatory true;
              }
          }
      }
  }
  
  grouping explicit-route-object-sr {
      container ero {
          list subobject {
        	  min-elements 1;
              leaf loose {
                  type boolean;
                  mandatory true;
              }
              leaf sid-type {
              	  type string;
              	  mandatory true;
              }
              leaf m-flag {
              	  type boolean;
              	  mandatory true;
              }
              leaf sid {
                  type uint32;
                  mandatory true;
              }
              leaf ip-address {
            	  type inet:ipv4-address;
            	  mandatory false;
              }
              leaf local-ip-address {
            	  type inet:ipv4-address;
            	  mandatory false;
              }
              leaf remote-ip-address {
            	  type inet:ipv4-address;
            	  mandatory false;
              }
          }
      }
  }

  grouping add-lsp-args {
      uses lsp-id;
      container arguments {
    	  uses lsp-attributes;
          uses endpoints-object;
          uses explicit-route-object;
      }
  }
  
  grouping add-lsp-sr-args {
  	  uses lsp-id;
  	  container arguments {
          uses lsp-attributes;
          container path-setup-type{
          	  leaf pst{
          	  	type uint32;
          	  	mandatory true;
          	  }
          }
  	  	
  	  	uses endpoints-object;
  	  	uses explicit-route-object-sr;
  	  }
  }

  grouping update-lsp-args {
      uses lsp-id;
      container arguments {
    	  uses lsp-attributes;
          uses explicit-route-object;
      }
  }

  grouping update-lsp-sr-args {
      uses lsp-id;
      container arguments {
    	  uses lsp-attributes;
          container path-setup-type{
          	  leaf pst{
          	  	type uint32;
          	  	mandatory true;
          	  }
          }
          uses explicit-route-object-sr;
      }
  }
  
  grouping remove-lsp-args {
      uses lsp-id;
  }

  grouping remove-lsp-sr-args {
      uses lsp-id;
  }
  
  
  rpc add-lsp {
	tailf:actionpoint ncsinternal {
	  tailf:internal;
	}
    input {
      uses add-lsp-args;
      leaf network-topology {
    	type string;
    	mandatory true;
      }
    }
    output {
      leaf operation-result {
        type string;
      }
    }
  }
  
  rpc add-lsp-sr {
	tailf:actionpoint ncsinternal {
	  tailf:internal;
	}
    input {
      uses add-lsp-sr-args;
      leaf network-topology {
    	type string;
    	mandatory true;
      }
    }
    output {
      leaf operation-result {
        type string;
      }
    }
  }

  rpc update-lsp {
	tailf:actionpoint ncsinternal {
	  tailf:internal;
	}
    input {
      uses update-lsp-args;
      leaf network-topology {
        type string;
        mandatory true;
      }
    }
    output {
  	  leaf operation-result {
        type string;
  	  }
    }
  }
  
  rpc update-lsp-sr {
	tailf:actionpoint ncsinternal {
	  tailf:internal;
	}
    input {
      uses update-lsp-sr-args;
      leaf network-topology {
        type string;
        mandatory true;
      }
    }
    output {
  	  leaf operation-result {
        type string;
  	  }
    }
  }

  rpc remove-lsp {
	tailf:actionpoint ncsinternal {
	  tailf:internal;
	}
    input {
      uses remove-lsp-args;
      leaf network-topology {
        type string;
        mandatory true;
      }
    }
    output {
      leaf operation-result {
        type string;
      }
    }
  }

  rpc remove-lsp-sr {
	tailf:actionpoint ncsinternal {
	  tailf:internal;
	}
    input {
      uses remove-lsp-sr-args;
      leaf network-topology {
        type string;
        mandatory true;
      }
    }
    output {
      leaf operation-result {
        type string;
      }
    }
}    
rpc get-tunnel-id {
	tailf:actionpoint ncsinternal {
	  tailf:internal;
	  }
	input {
	  uses lsp-id;
	  }
	output {
	  leaf tunnel-id {
	    type uint32;
	  }
    }
  }


}
